module "house-lockdown" {
  namespace "xml:ns:yang:house-lockdown";
  prefix "hl";
  description "house-lockdown module";
  contact "zvonimir.fras@sartura.hr";

  revision "2014-11-28" {
    description
      "Initial revision.";
  }

  rpc house-lockdown {
    description
      "Puts the entire house under lockdown. (or just tells it does ;))";
  }
}
